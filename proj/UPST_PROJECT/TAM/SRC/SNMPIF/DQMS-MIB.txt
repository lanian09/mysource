--
-- DQMS-MIB.my
-- MIB generated by MG-SOFT Visual MIB Builder Version 2.5 Build 225
-- Monday, July 06, 2009 at 19:19:03
--

	DQMS-MIB DEFINITIONS ::= BEGIN

		IMPORTS 
			enterprises			
				FROM RFC1155-SMI			
			TimeTicks, Integer32, OBJECT-TYPE, MODULE-IDENTITY, NOTIFICATION-TYPE			
				FROM SNMPv2-SMI;
	
	
		upresto MODULE-IDENTITY
			LAST-UPDATED "200906291625Z"
			ORGANIZATION
				"upresto, inc."
			CONTACT-INFO
				"Contact-info."
			DESCRIPTION
				"Description."
			REVISION "200906291626Z"
			DESCRIPTION
				"edit by hyhwang"
			::= { enterprises 28795 }
		
	
--
-- Node definitions
--
	
		product OBJECT IDENTIFIER ::= { upresto 1 }
		
		mgmt OBJECT IDENTIFIER ::= { upresto 2 }
		
		prTable OBJECT-TYPE
			SYNTAX SEQUENCE OF PrEntry
			MAX-ACCESS not-accessible
			STATUS current
			DESCRIPTION
				"Description."
			::= { mgmt 1 }
		
		prEntry OBJECT-TYPE
			SYNTAX PrEntry
			MAX-ACCESS not-accessible
			STATUS current
			DESCRIPTION
				"Description."
			INDEX { prIndex }
			::= { prTable 1 }
		
		PrEntry ::=
			SEQUENCE { 
				prIndex
					Integer32,
				prSystem
					OCTET STRING,
				prName
					OCTET STRING,
				prPid
					Integer32,
				prUptime
					TimeTicks,
				prStatus
					Integer32
			 }

		prIndex OBJECT-TYPE
			SYNTAX Integer32 (1..32)
			MAX-ACCESS read-only
			STATUS current
			DESCRIPTION
				"Description."
			::= { prEntry 1 }
		
		prSystem OBJECT-TYPE
			SYNTAX OCTET STRING
			MAX-ACCESS read-only
			STATUS current
			DESCRIPTION
				"Description."
			::= { prEntry 2 }
		
		prName OBJECT-TYPE
			SYNTAX OCTET STRING
			MAX-ACCESS read-only
			STATUS current
			DESCRIPTION
				"Description."
			::= { prEntry 3 }
		
		prPid OBJECT-TYPE
			SYNTAX Integer32
			MAX-ACCESS read-only
			STATUS current
			DESCRIPTION
				"Description."
			::= { prEntry 4 }
		
		prUptime OBJECT-TYPE
			SYNTAX TimeTicks
			MAX-ACCESS read-only
			STATUS current
			DESCRIPTION
				"Description."
			::= { prEntry 5 }
		
		prStatus OBJECT-TYPE
			SYNTAX Integer32 (0..100)
			MAX-ACCESS read-only
			STATUS current
			DESCRIPTION
				"Description."
			::= { prEntry 6 }
		
		dskTable OBJECT-TYPE
			SYNTAX SEQUENCE OF DskEntry
			MAX-ACCESS not-accessible
			STATUS current
			DESCRIPTION
				"Description."
			::= { mgmt 2 }
		
		dskEntry OBJECT-TYPE
			SYNTAX DskEntry
			MAX-ACCESS not-accessible
			STATUS current
			DESCRIPTION
				"Description."
			INDEX { dskIndex }
			::= { dskTable 1 }
		
		DskEntry ::=
			SEQUENCE { 
				dskIndex
					Integer32,
				dskSystem
					OCTET STRING,
				dskPath
					OCTET STRING,
				dskTotal
					Integer32,
				dskAvail
					Integer32,
				dskUsed
					Integer32,
				dskUsage
					Integer32
			 }

		dskIndex OBJECT-TYPE
			SYNTAX Integer32 (1..16)
			MAX-ACCESS read-only
			STATUS current
			DESCRIPTION
				"Description."
			::= { dskEntry 1 }
		
		dskSystem OBJECT-TYPE
			SYNTAX OCTET STRING
			MAX-ACCESS read-only
			STATUS current
			DESCRIPTION
				"Description."
			::= { dskEntry 2 }
		
		dskPath OBJECT-TYPE
			SYNTAX OCTET STRING
			MAX-ACCESS read-only
			STATUS current
			DESCRIPTION
				"Description."
			::= { dskEntry 3 }
		
		dskTotal OBJECT-TYPE
			SYNTAX Integer32
			MAX-ACCESS read-only
			STATUS current
			DESCRIPTION
				"Description."
			::= { dskEntry 4 }
		
		dskAvail OBJECT-TYPE
			SYNTAX Integer32
			MAX-ACCESS read-only
			STATUS current
			DESCRIPTION
				"Description."
			::= { dskEntry 5 }
		
		dskUsed OBJECT-TYPE
			SYNTAX Integer32
			MAX-ACCESS read-only
			STATUS current
			DESCRIPTION
				"Description."
			::= { dskEntry 6 }
		
		dskUsage OBJECT-TYPE
			SYNTAX Integer32 (0..100)
			MAX-ACCESS read-only
			STATUS current
			DESCRIPTION
				"Description."
			::= { dskEntry 7 }
		
		ethTable OBJECT-TYPE
			SYNTAX SEQUENCE OF EthEntry
			MAX-ACCESS not-accessible
			STATUS current
			DESCRIPTION
				"Description."
			::= { mgmt 3 }
		
		ethEntry OBJECT-TYPE
			SYNTAX EthEntry
			MAX-ACCESS not-accessible
			STATUS current
			DESCRIPTION
				"Description."
			INDEX { ethIndex }
			::= { ethTable 1 }
		
		EthEntry ::=
			SEQUENCE { 
				ethIndex
					Integer32,
				ethSystem
					OCTET STRING,
				ethPort
					Integer32,
				ethStatus
					Integer32
			 }

		ethIndex OBJECT-TYPE
			SYNTAX Integer32 (1..64)
			MAX-ACCESS read-only
			STATUS current
			DESCRIPTION
				"Description."
			::= { ethEntry 1 }
		
		ethSystem OBJECT-TYPE
			SYNTAX OCTET STRING
			MAX-ACCESS read-only
			STATUS current
			DESCRIPTION
				"Description."
			::= { ethEntry 2 }
		
		ethPort OBJECT-TYPE
			SYNTAX Integer32 (0..64)
			MAX-ACCESS read-only
			STATUS current
			DESCRIPTION
				"Description."
			::= { ethEntry 3 }
		
		ethStatus OBJECT-TYPE
			SYNTAX Integer32 (0..1)
			MAX-ACCESS read-only
			STATUS current
			DESCRIPTION
				"Description."
			::= { ethEntry 4 }
		
		memTable OBJECT-TYPE
			SYNTAX SEQUENCE OF MemEntry
			MAX-ACCESS not-accessible
			STATUS current
			DESCRIPTION
				"Description."
			::= { mgmt 4 }
		
		memEntry OBJECT-TYPE
			SYNTAX MemEntry
			MAX-ACCESS not-accessible
			STATUS current
			DESCRIPTION
				"Description."
			INDEX { memIndex }
			::= { memTable 1 }
		
		MemEntry ::=
			SEQUENCE { 
				memIndex
					Integer32,
				memSystem
					OCTET STRING,
				memTotal
					Integer32,
				memAvail
					Integer32,
				memUsed
					Integer32,
				memUsage
					Integer32
			 }

		memIndex OBJECT-TYPE
			SYNTAX Integer32 (1..16)
			MAX-ACCESS read-only
			STATUS current
			DESCRIPTION
				"Description."
			::= { memEntry 1 }
		
		memSystem OBJECT-TYPE
			SYNTAX OCTET STRING
			MAX-ACCESS read-only
			STATUS current
			DESCRIPTION
				"Description."
			::= { memEntry 2 }
		
		memTotal OBJECT-TYPE
			SYNTAX Integer32
			MAX-ACCESS read-only
			STATUS current
			DESCRIPTION
				"Description."
			::= { memEntry 3 }
		
		memAvail OBJECT-TYPE
			SYNTAX Integer32
			MAX-ACCESS read-only
			STATUS current
			DESCRIPTION
				"Description."
			::= { memEntry 4 }
		
		memUsed OBJECT-TYPE
			SYNTAX Integer32
			MAX-ACCESS read-only
			STATUS current
			DESCRIPTION
				"Description."
			::= { memEntry 5 }
		
		memUsage OBJECT-TYPE
			SYNTAX Integer32 (0..100)
			MAX-ACCESS read-only
			STATUS current
			DESCRIPTION
				"Description."
			::= { memEntry 6 }
		
		chnTable OBJECT-TYPE
			SYNTAX SEQUENCE OF ChnEntry
			MAX-ACCESS not-accessible
			STATUS current
			DESCRIPTION
				"Description."
			::= { mgmt 5 }
		
		chnEntry OBJECT-TYPE
			SYNTAX ChnEntry
			MAX-ACCESS not-accessible
			STATUS current
			DESCRIPTION
				"Description."
			INDEX { chnIndex }
			::= { chnTable 1 }
		
		ChnEntry ::=
			SEQUENCE { 
				chnIndex
					Integer32,
				chnSystem
					OCTET STRING,
				chnPort
					Integer32,
				chnStatus
					Integer32
			 }

		chnIndex OBJECT-TYPE
			SYNTAX Integer32 (1..128)
			MAX-ACCESS read-only
			STATUS current
			DESCRIPTION
				"Description."
			::= { chnEntry 1 }
		
		chnSystem OBJECT-TYPE
			SYNTAX OCTET STRING
			MAX-ACCESS read-only
			STATUS current
			DESCRIPTION
				"Description."
			::= { chnEntry 2 }
		
		chnPort OBJECT-TYPE
			SYNTAX Integer32
			MAX-ACCESS read-only
			STATUS current
			DESCRIPTION
				"Description."
			::= { chnEntry 3 }
		
		chnStatus OBJECT-TYPE
			SYNTAX Integer32 (0..1)
			MAX-ACCESS read-only
			STATUS current
			DESCRIPTION
				"Description."
			::= { chnEntry 4 }
		
		edTable OBJECT-TYPE
			SYNTAX SEQUENCE OF EdEntry
			MAX-ACCESS not-accessible
			STATUS current
			DESCRIPTION
				"Description."
			::= { mgmt 6 }
		
		edEntry OBJECT-TYPE
			SYNTAX EdEntry
			MAX-ACCESS not-accessible
			STATUS current
			DESCRIPTION
				"Description."
			INDEX { edIndex }
			::= { edTable 1 }
		
		EdEntry ::=
			SEQUENCE { 
				edIndex
					Integer32,
				edSystem
					OCTET STRING,
				edPort
					Integer32,
				edStatus
					Integer32
			 }

		edIndex OBJECT-TYPE
			SYNTAX Integer32 (1..128)
			MAX-ACCESS read-only
			STATUS current
			DESCRIPTION
				"Description."
			::= { edEntry 1 }
		
		edSystem OBJECT-TYPE
			SYNTAX OCTET STRING
			MAX-ACCESS read-only
			STATUS current
			DESCRIPTION
				"Description."
			::= { edEntry 2 }
		
		edPort OBJECT-TYPE
			SYNTAX Integer32 (0..16)
			MAX-ACCESS read-only
			STATUS current
			DESCRIPTION
				"Description."
			::= { edEntry 3 }
		
		edStatus OBJECT-TYPE
			SYNTAX Integer32 (0..1)
			MAX-ACCESS read-only
			STATUS current
			DESCRIPTION
				"Description."
			::= { edEntry 4 }
		
		queTable OBJECT-TYPE
			SYNTAX SEQUENCE OF QueEntry
			MAX-ACCESS not-accessible
			STATUS current
			DESCRIPTION
				"Description."
			::= { mgmt 7 }
		
		queEntry OBJECT-TYPE
			SYNTAX QueEntry
			MAX-ACCESS not-accessible
			STATUS current
			DESCRIPTION
				"Description."
			INDEX { queIndex }
			::= { queTable 1 }
		
		QueEntry ::=
			SEQUENCE { 
				queIndex
					Integer32,
				queSystem
					OCTET STRING,
				queTotal
					Integer32,
				queAvail
					Integer32,
				queUsed
					Integer32,
				queUsage
					Integer32
			 }

		queIndex OBJECT-TYPE
			SYNTAX Integer32 (1..128)
			MAX-ACCESS read-only
			STATUS current
			DESCRIPTION
				"Description."
			::= { queEntry 1 }
		
		queSystem OBJECT-TYPE
			SYNTAX OCTET STRING
			MAX-ACCESS read-only
			STATUS current
			DESCRIPTION
				"Description."
			::= { queEntry 2 }
		
		queTotal OBJECT-TYPE
			SYNTAX Integer32
			MAX-ACCESS read-only
			STATUS current
			DESCRIPTION
				"Description."
			::= { queEntry 3 }
		
		queAvail OBJECT-TYPE
			SYNTAX Integer32
			MAX-ACCESS read-only
			STATUS current
			DESCRIPTION
				"Description."
			::= { queEntry 4 }
		
		queUsed OBJECT-TYPE
			SYNTAX Integer32
			MAX-ACCESS read-only
			STATUS current
			DESCRIPTION
				"Description."
			::= { queEntry 5 }
		
		queUsage OBJECT-TYPE
			SYNTAX Integer32
			MAX-ACCESS read-only
			STATUS current
			DESCRIPTION
				"Description."
			::= { queEntry 6 }
		
		pwrTable OBJECT-TYPE
			SYNTAX SEQUENCE OF PwrEntry
			MAX-ACCESS not-accessible
			STATUS current
			DESCRIPTION
				"Description."
			::= { mgmt 8 }
		
		pwrEntry OBJECT-TYPE
			SYNTAX PwrEntry
			MAX-ACCESS not-accessible
			STATUS current
			DESCRIPTION
				"Description."
			INDEX { pwrIndex }
			::= { pwrTable 1 }
		
		PwrEntry ::=
			SEQUENCE { 
				pwrIndex
					Integer32,
				pwrSystem
					OCTET STRING,
				pwrId
					Integer32,
				pwrStatus
					Integer32
			 }

		pwrIndex OBJECT-TYPE
			SYNTAX Integer32
			MAX-ACCESS read-only
			STATUS current
			DESCRIPTION
				"Description."
			::= { pwrEntry 1 }
		
		pwrSystem OBJECT-TYPE
			SYNTAX OCTET STRING
			MAX-ACCESS read-write
			STATUS current
			DESCRIPTION
				"Description."
			::= { pwrEntry 2 }
		
		pwrId OBJECT-TYPE
			SYNTAX Integer32
			MAX-ACCESS read-only
			STATUS current
			DESCRIPTION
				"Description."
			::= { pwrEntry 3 }
		
		pwrStatus OBJECT-TYPE
			SYNTAX Integer32 (0..1)
			MAX-ACCESS read-only
			STATUS current
			DESCRIPTION
				"Description."
			::= { pwrEntry 4 }
		
		fanTable OBJECT-TYPE
			SYNTAX SEQUENCE OF FanEntry
			MAX-ACCESS not-accessible
			STATUS current
			DESCRIPTION
				"Description."
			::= { mgmt 9 }
		
		fanEntry OBJECT-TYPE
			SYNTAX FanEntry
			MAX-ACCESS not-accessible
			STATUS current
			DESCRIPTION
				"Description."
			INDEX { fanIndex }
			::= { fanTable 1 }
		
		FanEntry ::=
			SEQUENCE { 
				fanIndex
					Integer32,
				fanSystem
					OCTET STRING,
				fanId
					Integer32,
				fanStatus
					Integer32
			 }

		fanIndex OBJECT-TYPE
			SYNTAX Integer32
			MAX-ACCESS read-only
			STATUS current
			DESCRIPTION
				"Description."
			::= { fanEntry 1 }
		
		fanSystem OBJECT-TYPE
			SYNTAX OCTET STRING
			MAX-ACCESS read-only
			STATUS current
			DESCRIPTION
				"Description."
			::= { fanEntry 2 }
		
		fanId OBJECT-TYPE
			SYNTAX Integer32
			MAX-ACCESS read-only
			STATUS current
			DESCRIPTION
				"Description."
			::= { fanEntry 3 }
		
		fanStatus OBJECT-TYPE
			SYNTAX Integer32 (0..1)
			MAX-ACCESS read-only
			STATUS current
			DESCRIPTION
				"Description."
			::= { fanEntry 4 }
		
		ntpTable OBJECT-TYPE
			SYNTAX SEQUENCE OF NtpEntry
			MAX-ACCESS not-accessible
			STATUS current
			DESCRIPTION
				"Description."
			::= { mgmt 10 }
		
		ntpEntry OBJECT-TYPE
			SYNTAX NtpEntry
			MAX-ACCESS not-accessible
			STATUS current
			DESCRIPTION
				"Description."
			INDEX { ntpIndex }
			::= { ntpTable 1 }
		
		NtpEntry ::=
			SEQUENCE { 
				ntpIndex
					Integer32,
				ntpSystem
					OCTET STRING,
				ntpId
					Integer32,
				ntpStatus
					Integer32
			 }

		ntpIndex OBJECT-TYPE
			SYNTAX Integer32
			MAX-ACCESS read-only
			STATUS current
			DESCRIPTION
				"Description."
			::= { ntpEntry 1 }
		
		ntpSystem OBJECT-TYPE
			SYNTAX OCTET STRING
			MAX-ACCESS read-only
			STATUS current
			DESCRIPTION
				"Description."
			::= { ntpEntry 2 }
		
		ntpId OBJECT-TYPE
			SYNTAX Integer32
			MAX-ACCESS read-only
			STATUS current
			DESCRIPTION
				"Description."
			::= { ntpEntry 3 }
		
		ntpStatus OBJECT-TYPE
			SYNTAX Integer32 (0..1)
			MAX-ACCESS read-only
			STATUS current
			DESCRIPTION
				"Description."
			::= { ntpEntry 4 }
		
		upstTraps OBJECT IDENTIFIER ::= { mgmt 11 }
		
		start NOTIFICATION-TYPE
			STATUS current
			DESCRIPTION
				"Description."
			::= { upstTraps 1 }
		
		stop NOTIFICATION-TYPE
			STATUS current
			DESCRIPTION
				"Description."
			::= { upstTraps 2 }
		
	
	END

--
-- DQMS-MIB.my
--
